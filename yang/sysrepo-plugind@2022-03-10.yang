module sysrepo-plugind {
  namespace "urn:sysrepo:plugind";
  prefix srpd;

  revision 2022-03-10 {
    description
      "Added info about loaded plugins.";
  }
  revision 2020-12-10 {
    description
      "Initial revision.";
  }

  container sysrepo-plugind {
    container plugin-order {
      description
        "The order in which to run plugins from the sysrepo-plugind.";
      leaf-list plugin {
        type string;
        ordered-by user;
        description
          "The name of the plugin file, which may or may not include the extension.";
      }
    }
    container loaded-plugins {
      config false;
      description
        "Names of all the loaded (initialized) plugins.";
      leaf-list plugin {
        type string;
        description
          "Name of a loaded plugin.";
      }
    }
  }
}
